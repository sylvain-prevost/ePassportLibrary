MRTDSecurityDatagroups DEFINITIONS IMPLICIT TAGS ::= BEGIN

IMPORTS
    ContentInfo, SignedData
        FROM CryptographicMessageSyntax2004 {iso (1) member-body (2) us (840) rsadsi (113549) pkcs (1) pkcs-9 (9) smime (16) modules (0) cms-2004 (24)};    

DGSOD ::= [APPLICATION 23] IMPLICIT SEQUENCE {
    sod     ContentInfo
}

END
