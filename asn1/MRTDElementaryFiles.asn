MRTDElementaryFiles DEFINITIONS IMPLICIT TAGS ::= BEGIN

IMPORTS
    Time, Validity, AlgorithmIdentifier, SubjectPublicKeyInfo
        FROM PKIX1Explicit88 {iso (1) identified-organization (3) dod (6) internet (1) security (5) mechanisms (5) pkix (7) id-mod (0) id-pkix1-explicit (18)}
    SignedData
        FROM CryptographicMessageSyntax2004 {iso (1) member-body (2) us (840) rsadsi (113549) pkcs (1) pkcs-9 (9) smime (16) modules (0) cms-2004 (24)};            

-------------------------------
-------------------------------
-------------------------------

-- Document security object
EFSOD ::= [APPLICATION 23] IMPLICIT SEQUENCE {
    sod     SodContentInfo
}

-- Common data elements
EFCOM ::= [APPLICATION 0] IMPLICIT SEQUENCE {
    ldsVersionNumber           [APPLICATION 1] NumericString (SIZE(4)),
    unicodeVersionNumber       [APPLICATION 54] NumericString (SIZE(6)),
    datagroupList              [APPLICATION 28] OCTET STRING
}

-- MRZ datagroup
DG1 ::= [APPLICATION 1] IMPLICIT SEQUENCE {
    mrz     [APPLICATION 31] IMPLICIT IA5String
}

-- Face datagroup
DG2 ::= [APPLICATION 21] IMPLICIT SEQUENCE {
    biometricInfoGroupTemplate BiometricInfoGroupTemplate
}

-- FingerPrint datagroup
DG3 ::= [APPLICATION 3] IMPLICIT SEQUENCE {
    biometricInfoGroupTemplate BiometricInfoGroupTemplate
}

-- Iris datagroup
DG4 ::= [APPLICATION 22] IMPLICIT SEQUENCE {
    biometricInfoGroupTemplate BiometricInfoGroupTemplate
}

-- Security Options datagroup
DG14 ::= [APPLICATION 14] IMPLICIT SEQUENCE {
    securityInfos SecurityInfos
}

-- Active Authentication Public Key Info datagroup
DG15 ::= [APPLICATION 15] IMPLICIT SEQUENCE {
    activeAuthenticationPublicKeyInfo   ActiveAuthenticationPublicKeyInfo
}

-------------------------------
-------------------------------
-------------------------------

SodContentInfo ::= SEQUENCE {
    oid            OBJECT IDENTIFIER, -- must map to 1.2.840.113549.1.7.2 (signed data)
    signedData     [0] EXPLICIT SignedData
}

BiometricDataBlock ::= OCTET STRING

BiometricType ::= ENUMERATED {
    multiple                (1),
    facialFeatures          (2),
    voice                   (4),
    fingerPrint             (8),
    iris                    (16),
    retina                  (32),
    handGeometry            (64),
    signatureDynamics       (128),
    keystrokDynamics        (256),
    lipMovement             (512),
    thermalFaceImage        (1024),
    thermalHandImage        (2048),
    gait                    (4096),
    bodyOdor                (8192),
    dna                     (16384),
    earShape                (32768),
    fingerGeometry          (65536),
    palmGeometry            (131072),
    veinPattern             (262144)
}

BiometricHeaderTemplate ::= SEQUENCE {
    headerVersion  [0] OCTET STRING OPTIONAL,
    biometricType  [1] BiometricType OPTIONAL,
    biometricSubType [2] OCTET STRING OPTIONAL,
    creationDateTime [3] Time OPTIONAL,
    validityPeriod [5] Validity OPTIONAL,
    creator        [6] OCTET STRING OPTIONAL,
    formatOwner    [7] OCTET STRING (SIZE (2)),
    formatType     [8] OCTET STRING (SIZE (2))
}

BiometricInfoTemplate ::= [APPLICATION 96] IMPLICIT SEQUENCE {
    biometricHeaderTemplate [1] BiometricHeaderTemplate,
    biometricDataBlock [APPLICATION 46] IMPLICIT BiometricDataBlock
}

BiometricInfoGroupTemplate ::= [APPLICATION 97] IMPLICIT SEQUENCE {
    numberOfInstances INTEGER,
    biometricInfoTemplate ANY -- (numberOfInstances x BiometricInfoTemplate)
}

SecurityInfo ::= SEQUENCE {
    protocol            OBJECT IDENTIFIER,
    requiredData        ANY DEFINED BY protocol,
    optionalData        ANY DEFINED BY protocol OPTIONAL
}

SecurityInfos ::= SET OF SecurityInfo

PACEInfo ::= SEQUENCE {
    protocol                        OBJECT IDENTIFIER,
    version                         INTEGER, -- MUST be 2
    parameterId                     INTEGER OPTIONAL
}

PACEDomainParameterInfo ::= SEQUENCE {
    protocol                        OBJECT IDENTIFIER,
    domainParameter                 AlgorithmIdentifier,
    parameterId                     INTEGER OPTIONAL
}

ActiveAuthenticationInfo ::= SEQUENCE {
    protocol                        OBJECT IDENTIFIER,
    version                         INTEGER, -- MUST be 1
    signatureAlgorithm              OBJECT IDENTIFIER
}

ChipAuthenticationInfo ::= SEQUENCE {
    protocol                        OBJECT IDENTIFIER,
    version                         INTEGER, -- MUST be 1
    keyId                           INTEGER OPTIONAL
}

ChipAuthenticationPublicKeyInfo ::= SEQUENCE {
    protocol                        OBJECT IDENTIFIER,
    chipAuthenticationPublicKey     SubjectPublicKeyInfo,
    keyId                           INTEGER OPTIONAL
}

TerminalAuthenticationInfo ::= SEQUENCE {
    protocol                        OBJECT IDENTIFIER,
    version                         INTEGER -- MUST be 1
}

EFDIRInfo ::= SEQUENCE {
    protocol                        OBJECT IDENTIFIER,
    eFDIR                           OCTET STRING
}

ActiveAuthenticationPublicKeyInfo ::= SubjectPublicKeyInfo

END
